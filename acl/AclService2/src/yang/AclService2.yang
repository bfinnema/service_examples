module AclService2 {

  namespace "http://example.com/AclService2";
  prefix AclService2;

  import ietf-inet-types {
    prefix inet;
  }
  import tailf-common {
    prefix tailf;
  }
  import tailf-ncs {
    prefix ncs;
  }

  description
    "ACL service";

  revision 2023-06-15 {
    description
      "Initial revision.";
  }

  list AclService2 {
    description "This is an RFS skeleton service";

    key name;
    leaf name {
      tailf:info "Unique service id";
      tailf:cli-allow-range;
      type string;
    }

    uses ncs:service-data;
    ncs:servicepoint AclService2-servicepoint;

    leaf-list device {
      tailf:info "List of devices to run the service on";
      type leafref {
        path "/ncs:devices/ncs:device/ncs:name";
      }
    }

    leaf interface_id {
      tailf:info "Interface to change Ex 0";
      type string;
    }

    leaf interface_subnet {
      tailf:info "Ip address of the interface Ex 192.168.1.20";
      type inet:ipv4-address;
    }

    leaf acl_name {
      tailf:info "Name of the Access List (ACL) Ex ACL1";
      type string;
    }

    leaf acl_line {
      tailf:info "Line number of the ACL Ex 10";
      type uint32;
    }

    leaf acl_subnet_address {
      tailf:info "IP address to use in the ACL line Ex 172.16.0.0";
      type inet:ipv4-address;
    }
  }
}
